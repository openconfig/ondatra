module openconfig-simple {
  prefix "ocs";
  namespace "urn:ocs";
  description
    "A simple test module with the OpenConfig structure.";

  import openconfig-remote { prefix "ocr"; }

  grouping parent-config {
    leaf one { type string; }
    leaf three {
      type enumeration {
        enum ONE;
        enum TWO;
      }
    }
    leaf four {
      type binary;
    }
    leaf five {
      type ieeefloat32;
    }
  }

  typedef ieeefloat32 {
    type binary {
      length "4";
    }
    description
      "An IEEE 32-bit floating point number. The format of this number
      is of the form:
        1-bit  sign
        8-bit  exponent
        23-bit fraction
      The floating point value is calculated using:
        (-1)**S * 2**(Exponent-127) * (1+Fraction)";
  }

  container parent {
    container child {
      container config {
        uses parent-config;
      }
      container state {
        uses parent-config;
        leaf two { type string; }
      }
    }
  }

  uses ocr:a-grouping;
}
